from __future__ import annotations

from pathlib import Path

import FreeCAD as fc
from FreeCAD import Placement
from FreeCAD import Vector

import FreeCADGui as fcgui


from freecad.cross.freecad_utils import make_group
from freecad.cross.robot import make_robot
from freecad.cross.wb_utils import ros_name

from cross_macro_utils import add_cross_link
from cross_macro_utils import add_joint
from cross_macro_utils import get_object
from cross_macro_utils import rotx
from cross_macro_utils import roty
from cross_macro_utils import rotz


def make_fc_links():
    doc = fc.activeDocument()
    dir = Path(doc.FileName).parent
    parts_doc = fc.open(str(dir / 'mobile_robot-parts.fcstd'))
    fc.setActiveDocument(doc.Name)

    visual_undercarriage = doc.addObject('App::Link', 'visual_undercarriage')
    visual_undercarriage.LinkedObject = get_object(parts_doc, 'undercarriage')

    visual_hub = doc.addObject('App::Link', 'visual_hub')
    visual_hub.LinkedObject = get_object(parts_doc, 'hub')

    visual_wheel = doc.addObject('App::Link', 'visual_wheel')
    visual_wheel.LinkedObject = get_object(parts_doc, 'wheel')

    collision_undercarriage = doc.addObject('App::Link', 'collision_undercarriage')
    collision_undercarriage.LinkedObject = get_object(parts_doc, 'collision_undercarriage')

    collision_hub = doc.addObject('App::Link', 'collision_hub')
    collision_hub.LinkedObject = get_object(parts_doc, 'collision_hub')

    collision_wheel = doc.addObject('App::Link', 'collision_wheel')
    collision_wheel.LinkedObject = get_object(parts_doc, 'collision_wheel')

    parts_group = make_group(doc, 'Parts')
    parts_group.addObject(visual_undercarriage)
    parts_group.addObject(visual_hub)
    parts_group.addObject(visual_wheel)
    parts_group.addObject(collision_undercarriage)
    parts_group.addObject(collision_hub)
    parts_group.addObject(collision_wheel)
    parts_group.Visibility = False

    doc.recompute()


def make_mobile_robot():
    doc = fc.activeDocument()

    robot = make_robot('mobile_robot')

    undercarriage = add_cross_link(robot, 'undercarriage',
                                   'visual_undercarriage', 'collision_undercarriage',
                                   Placement(Vector(), rotz(-90.0)))

    hub_hr = add_cross_link(robot, 'hub_hr', 'visual_hub', 'collision_hub',
                            Placement(Vector(), rotz(-90.0)))

    hub_hl = add_cross_link(robot, 'hub_hl', 'visual_hub', 'collision_hub',
                            Placement(Vector(), rotz(-90.0)))

    hub_br = add_cross_link(robot, 'hub_br', 'visual_hub', 'collision_hub',
                            Placement(Vector(), rotz(-90.0)))

    hub_bl = add_cross_link(robot, 'hub_bl', 'visual_hub', 'collision_hub',
                            Placement(Vector(), rotz(-90.0)))

    wheel_hr = add_cross_link(robot, 'wheel_hr', 'visual_wheel', 'collision_wheel',
                              Placement(Vector(0.0, 0.0, 10.0), rotz(-90.0) * rotx(-180.0)))

    wheel_hl = add_cross_link(robot, 'wheel_hl', 'visual_wheel', 'collision_wheel',
                              Placement(Vector(0.0, 0.0, 10.0), rotz(-90.0) * rotx(-180.0)))

    wheel_br = add_cross_link(robot, 'wheel_br', 'visual_wheel', 'collision_wheel',
                              Placement(Vector(0.0, 0.0, 10.0), rotz(-90.0) * rotx(-180.0)))

    wheel_bl = add_cross_link(robot, 'wheel_bl', 'visual_wheel', 'collision_wheel',
                              Placement(Vector(0.0, 0.0, 10.0), rotz(-90.0) * rotx(-180.0)))

    joint_hub_hr = add_joint(robot, 'undercarriage-hub_hr',
                             Placement(Vector(-300.0, -200.0, -5.0), rotx(180.0)))

    joint_hub_hl = add_joint(robot, 'undercarriage-hub_hl',
                             Placement(Vector(-300.0, 200.0, -5.0), roty(180.0)))

    joint_hub_br = add_joint(robot, 'undercarriage-hub_br',
                             Placement(Vector(300.0, -200.0, -5.0), rotx(180.0)))

    joint_hub_bl = add_joint(robot, 'undercarriage-hub_bl',
                             Placement(Vector(300.0, 200.0, -5.0), roty(180.0)))

    joint_wheel_hr = add_joint(robot, 'hub_hr-wheel_hr',
                               Placement(Vector(0.0, 20.0, 90.0), rotx(-90.0)))

    joint_wheel_hl = add_joint(robot, 'hub_hl-wheel_hl',
                               Placement(Vector(0.0, 20.0, 90.0), rotx(-90.0)))

    joint_wheel_br = add_joint(robot, 'hub_br-wheel_br',
                               Placement(Vector(0.0, 20.0, 90.0), rotx(-90.0)))

    joint_wheel_bl = add_joint(robot, 'hub_bl-wheel_bl',
                               Placement(Vector(0.0, 20.0, 90.0), rotx(-90.0)))

    # Set visibilities after links are added.
    robot.ViewObject.ShowCollision = False
    robot.ViewObject.ShowJointAxes = True
    robot.ViewObject.ShowReal = False
    robot.ViewObject.ShowVisual = True

    # Set parenthoods after links are added.
    joint_hub_hr.Parent = ros_name(undercarriage)
    joint_hub_hr.Child = ros_name(hub_hr)

    joint_hub_hl.Parent = ros_name(undercarriage)
    joint_hub_hl.Child = ros_name(hub_hl)

    joint_hub_br.Parent = ros_name(undercarriage)
    joint_hub_br.Child = ros_name(hub_br)

    joint_hub_bl.Parent = ros_name(undercarriage)
    joint_hub_bl.Child = ros_name(hub_bl)

    joint_wheel_hr.Parent = ros_name(hub_hr)
    joint_wheel_hr.Child = ros_name(wheel_hr)

    joint_wheel_hl.Parent = ros_name(hub_hl)
    joint_wheel_hl.Child = ros_name(wheel_hl)

    joint_wheel_br.Parent = ros_name(hub_br)
    joint_wheel_br.Child = ros_name(wheel_br)

    joint_wheel_bl.Parent = ros_name(hub_bl)
    joint_wheel_bl.Child = ros_name(wheel_bl)

    doc.recompute()


make_fc_links()
make_mobile_robot()
fcgui.SendMsgToActiveView('ViewFit')
