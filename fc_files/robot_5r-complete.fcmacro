from pathlib import Path

import FreeCAD as fc
import FreeCADGui as fcgui

from FreeCAD import Placement, Rotation, Vector

from freecad.cross.freecad_utils import make_group
from freecad.cross.robot import make_robot
from freecad.cross.wb_utils import ros_name


from cross_macro_utils import add_cross_link
from cross_macro_utils import add_joint
from cross_macro_utils import get_object
from cross_macro_utils import rotx
from cross_macro_utils import roty
from cross_macro_utils import rotz


def make_links():
    doc = fc.activeDocument()
    dir = Path(doc.FileName).parent
    robot5r_parts_doc = fc.open(str(dir / 'robot_5r-parts.fcstd'))
    fingers_parts_doc = fc.open(str(dir / 'parallel_fingers-parts.fcstd'))
    fc.setActiveDocument(doc.Name)

    visual_base_ = doc.addObject('App::Link', 'visual_base_')
    visual_base_.LinkedObject = get_object(robot5r_parts_doc, 'base')

    visual_shoulder_ = doc.addObject('App::Link', 'visual_shoulder_')
    visual_shoulder_.LinkedObject = get_object(robot5r_parts_doc, 'shoulder')

    visual_arm_ = doc.addObject('App::Link', 'visual_arm_')
    visual_arm_.LinkedObject = get_object(robot5r_parts_doc, 'arm/forearm')

    visual_forearm_ = doc.addObject('App::Link', 'visual_forearm_')
    visual_forearm_.LinkedObject = get_object(robot5r_parts_doc, 'arm/forearm')

    visual_hand_ = doc.addObject('App::Link', 'visual_hand_')
    visual_hand_.LinkedObject = get_object(robot5r_parts_doc, 'hand')

    visual_palm_ = doc.addObject('App::Link', 'visual_palm_')
    visual_palm_.LinkedObject = get_object(fingers_parts_doc, 'palm')

    visual_right_finger_ = doc.addObject('App::Link', 'visual_right_finger_')
    visual_right_finger_.LinkedObject = get_object(fingers_parts_doc, 'finger')

    visual_left_finger_ = doc.addObject('App::Link', 'visual_left_finger_')
    visual_left_finger_.LinkedObject = get_object(fingers_parts_doc, 'finger')

    collision_base_ = doc.addObject('App::Link', 'collision_base_')
    collision_base_.LinkedObject = get_object(robot5r_parts_doc, 'base_collision')

    collision_shoulder_ = doc.addObject('App::Link', 'collision_shoulder_')
    collision_shoulder_.LinkedObject = get_object(robot5r_parts_doc, 'shoulder_collision')

    collision_arm_ = doc.addObject('App::Link', 'collision_arm_')
    collision_arm_.LinkedObject = get_object(robot5r_parts_doc, 'arm_collision')

    collision_forearm_ = doc.addObject('App::Link', 'collision_forearm_')
    collision_forearm_.LinkedObject = get_object(robot5r_parts_doc, 'arm_collision')

    collision_hand_ = doc.addObject('App::Link', 'collision_hand_')
    collision_hand_.LinkedObject = get_object(robot5r_parts_doc, 'hand_collision')

    collision_palm_ = doc.addObject('App::Link', 'collision_palm_')
    collision_palm_.LinkedObject = get_object(fingers_parts_doc, 'palm_collision')

    collision_right_finger_ = doc.addObject('App::Link', 'collision_right_finger_')
    collision_right_finger_.LinkedObject = get_object(fingers_parts_doc, 'finger_collision')

    collision_left_finger_ = doc.addObject('App::Link', 'collision_left_finger_')
    collision_left_finger_.LinkedObject = get_object(fingers_parts_doc, 'finger_collision')

    parts_group = make_group(doc, 'Parts')
    parts_group.addObject(visual_base_)
    parts_group.addObject(visual_shoulder_)
    parts_group.addObject(visual_arm_)
    parts_group.addObject(visual_forearm_)
    parts_group.addObject(visual_hand_)
    parts_group.addObject(visual_palm_)
    parts_group.addObject(visual_right_finger_)
    parts_group.addObject(visual_left_finger_)
    parts_group.addObject(collision_base_)
    parts_group.addObject(collision_shoulder_)
    parts_group.addObject(collision_arm_)
    parts_group.addObject(collision_forearm_)
    parts_group.addObject(collision_hand_)
    parts_group.addObject(collision_palm_)
    parts_group.addObject(collision_right_finger_)
    parts_group.addObject(collision_left_finger_)
    parts_group.Visibility = False

    doc.recompute()


def make_robot_5r_complete():
    doc = fc.activeDocument()

    robot = make_robot('robot_5r-complete')
    robot.Label2 = 'robot_5r-complete'

    base_link = add_cross_link(robot, 'base_link',
                               'visual_base_', 'collision_base_',
                               Placement(Vector(0.0, 0.0, 0.0),
                                         Rotation(0.0, 0.0, 0.0, 1.0)))

    shoulder = add_cross_link(robot, 'shoulder',
                              'visual_shoulder_', 'collision_shoulder_',
                              Placement(Vector(0.0, 0.0, 0.0),
                                        Rotation(0.0, 0.0, 0.0, 1.0)))

    arm = add_cross_link(robot, 'arm',
                         'visual_arm_', 'collision_arm_',
                         Placement(Vector(0.0, -45.0, 60.0), rotx(-90.0)))

    forearm = add_cross_link(robot, 'forearm',
                             'visual_forearm_', 'collision_forearm_',
                             Placement(Vector(0.0, 45.0, 60.0),
                                       rotz(180.0) * rotx(-90.0)))

    hand = add_cross_link(robot, 'hand',
                          'visual_hand_', 'collision_hand_',
                          Placement(Vector(0.0, 0.0, 0.0),
                                    Rotation(0.0, 0.0, 0.0, 1.0)))

    palm = add_cross_link(robot, 'palm',
                          'visual_palm_', 'collision_palm_',
                          Placement(Vector(0.0, 0.0, 0.0),
                                    Rotation(0.0, 0.0, 0.0, 1.0)))

    right_finger = add_cross_link(robot, 'right_finger',
                                  'visual_right_finger_', 'collision_right_finger_',
                                  Placement(Vector(0.0, 0.0, 0.0), roty(90.0)))

    left_finger = add_cross_link(robot, 'left_finger',
                                 'visual_left_finger_', 'collision_left_finger_',
                                 Placement(Vector(0.0, 0.0, 0.0), roty(90.0)))

    base_shoulder = add_joint(robot, 'base-shoulder',
                              Placement(Vector(0.0, 0.0, 20.0),
                                        Rotation(0.0, 0.0, 0.0, 1.0)))

    shoulder_arm = add_joint(robot, 'shoulder-arm',
                             Placement(Vector(0.0, -60.0, 70.0), rotx(90.0)))

    arm_forearm = add_joint(robot, 'arm-forearm',
                            Placement(Vector(0.0, 700.0, 0.0), rotx(180.0)))

    forearm_hand = add_joint(robot, 'forearm-hand',
                             Placement(Vector(0.0, -700.0, 0.0), roty(180.0)))

    hand_palm = add_joint(robot, 'hand-palm',
                          Placement(Vector(0.0, -60.0, 45.0), rotx(90.0)))

    palm_right_finger = add_joint(robot, 'palm-right_finger',
                                  Placement(Vector(0.0, -5.0, 40.0),
                                            rotx(90.0)))
    palm_right_finger.Type = 'prismatic'

    palm_left_finger = add_joint(robot, 'palm-left_finger',
                                 Placement(Vector(0.0, 5.0, 40.0),
                                           rotz(180) * rotx(90)))
    palm_left_finger.Type = 'prismatic'
    palm_left_finger.Mimic = True
    palm_left_finger.MimickedJoint = palm_right_finger

    # Set visibilities after links are added.
    robot.ViewObject.ShowCollision = False
    robot.ViewObject.ShowJointAxes = True
    robot.ViewObject.ShowReal = False
    robot.ViewObject.ShowVisual = True

    base_shoulder.Parent = ros_name(base_link)
    base_shoulder.Child = ros_name(shoulder)

    shoulder_arm.Parent = ros_name(shoulder)
    shoulder_arm.Child = ros_name(arm)

    arm_forearm.Parent = ros_name(arm)
    arm_forearm.Child = ros_name(forearm)

    forearm_hand.Parent = ros_name(forearm)
    forearm_hand.Child = ros_name(hand)

    hand_palm.Parent = ros_name(hand)
    hand_palm.Child = ros_name(palm)

    palm_right_finger.Parent = ros_name(palm)
    palm_right_finger.Child = ros_name(right_finger)

    palm_left_finger.Parent = ros_name(palm)
    palm_left_finger.Child = ros_name(left_finger)

    doc.recompute()


make_links()
make_robot_5r_complete()
fcgui.SendMsgToActiveView('ViewFit')
