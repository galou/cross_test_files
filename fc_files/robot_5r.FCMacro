from pathlib import Path

import FreeCAD as fc
from FreeCAD import Placement, Rotation, Vector

import FreeCADGui as fcgui


from freecad.cross.freecad_utils import make_group
from freecad.cross.robot_proxy import make_robot
from freecad.cross.wb_utils import ros_name

from cross_macro_utils import add_cross_link
from cross_macro_utils import add_joint
from cross_macro_utils import get_object
from cross_macro_utils import rotx
from cross_macro_utils import roty
from cross_macro_utils import rotz


def make_links():
    doc = fc.activeDocument()
    dir = Path(doc.FileName).parent
    parts_doc = fc.open(str(dir / 'robot_5r-parts.FCStd'))
    fc.setActiveDocument(doc.Name)

    visual_base_ = doc.addObject('App::Link', 'visual_base_')
    visual_base_.LinkedObject = get_object(parts_doc, 'base')

    visual_shoulder_ = doc.addObject('App::Link', 'visual_shoulder_')
    visual_shoulder_.LinkedObject = get_object(parts_doc, 'shoulder')

    visual_arm_ = doc.addObject('App::Link', 'visual_arm_')
    visual_arm_.LinkedObject = get_object(parts_doc, 'arm/forearm')

    visual_forearm_ = doc.addObject('App::Link', 'visual_forearm_')
    visual_forearm_.LinkedObject = get_object(parts_doc, 'arm/forearm')

    visual_hand_ = doc.addObject('App::Link', 'visual_hand_')
    visual_hand_.LinkedObject = get_object(parts_doc, 'hand')

    collision_base_ = doc.addObject('App::Link', 'collision_base_')
    collision_base_.LinkedObject = get_object(parts_doc, 'base_collision')

    collision_shoulder_ = doc.addObject('App::Link', 'collision_shoulder_')
    collision_shoulder_.LinkedObject = get_object(parts_doc, 'shoulder_collision')

    collision_arm_ = doc.addObject('App::Link', 'collision_arm_')
    collision_arm_.LinkedObject = get_object(parts_doc, 'arm_collision')

    collision_forearm_ = doc.addObject('App::Link', 'collision_forearm_')
    collision_forearm_.LinkedObject = get_object(parts_doc, 'arm_collision')

    collision_hand_ = doc.addObject('App::Link', 'collision_hand_')
    collision_hand_.LinkedObject = get_object(parts_doc, 'hand_collision')

    parts_group = make_group(doc, 'Parts')
    parts_group.addObject(visual_base_)
    parts_group.addObject(visual_shoulder_)
    parts_group.addObject(visual_arm_)
    parts_group.addObject(visual_forearm_)
    parts_group.addObject(visual_hand_)
    parts_group.addObject(collision_base_)
    parts_group.addObject(collision_shoulder_)
    parts_group.addObject(collision_arm_)
    parts_group.addObject(collision_forearm_)
    parts_group.addObject(collision_hand_)
    parts_group.Visibility = False

    doc.recompute()


def make_robot_5r():
    doc = fc.activeDocument()

    robot = make_robot('robot_5r')
    robot.Label2 = 'robot_5r'

    base_link = add_cross_link(robot, 'base_link',
                               'visual_base_', 'collision_base_',
                               Placement(Vector(0.0, 0.0, 0.0),
                                         Rotation(0.0, 0.0, 0.0, 1.0)))

    shoulder = add_cross_link(robot, 'shoulder',
                              'visual_shoulder_', 'collision_shoulder_',
                              Placement(Vector(0.0, 0.0, 0.0),
                                        Rotation(0.0, 0.0, 0.0, 1.0)))

    arm = add_cross_link(robot, 'arm',
                         'visual_arm_', 'collision_arm_',
                         Placement(Vector(0.0, -45.0, 60.0), rotx(-90.0)))

    forearm = add_cross_link(robot, 'forearm',
                             'visual_forearm_', 'collision_forearm_',
                             Placement(Vector(0.0, 45.0, 60.0),
                                       rotz(180.0) * rotx(-90.0)))

    hand = add_cross_link(robot, 'hand',
                          'visual_hand_', 'collision_hand_',
                          Placement(Vector(0.0, 0.0, 0.0),
                                    Rotation(0.0, 0.0, 0.0, 1.0)))

    base_shoulder = add_joint(robot, 'base-shoulder',
                              Placement(Vector(0.0, 0.0, 20.0),
                                        Rotation(0.0, 0.0, 0.0, 1.0)))

    shoulder_arm = add_joint(robot, 'shoulder-arm',
                             Placement(Vector(0.0, -60.0, 70.0), rotx(90.0)))

    arm_forearm = add_joint(robot, 'arm-forearm',
                            Placement(Vector(0.0, 700.0, 0.0), rotx(180.0)))

    forearm_hand = add_joint(robot, 'forearm-hand',
                             Placement(Vector(0.0, -700.0, 0.0), roty(180.0)))

    # Set visibilities after links are added.
    robot.ViewObject.ShowCollision = False
    robot.ViewObject.ShowJointAxes = True
    robot.ViewObject.ShowReal = False
    robot.ViewObject.ShowVisual = True

    base_shoulder.Parent = ros_name(base_link)
    base_shoulder.Child = ros_name(shoulder)

    shoulder_arm.Parent = ros_name(shoulder)
    shoulder_arm.Child = ros_name(arm)

    arm_forearm.Parent = ros_name(arm)
    arm_forearm.Child = ros_name(forearm)

    forearm_hand.Parent = ros_name(forearm)
    forearm_hand.Child = ros_name(hand)

    doc.recompute()


make_links()
make_robot_5r()
fcgui.SendMsgToActiveView('ViewFit')
